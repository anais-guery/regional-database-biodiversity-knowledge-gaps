FME workspace knowledge_gaps_identification.fmw

Parameters:
- SourceDataset_CSV2_7 =   # Source CSV (Comma Separated Value) File(s)
- SourceDataset_SHAPEFILE_2 =   # Source Esri Shapefile(s)
- DestDataset_SHAPEFILE_3 =   # Destination Esri Shapefile Folder
- SourceDataset_CSV2 =   # Source CSV (Comma Separated Value) File(s)

Readers:
- CSV2_1: CSV2 from $(SourceDataset_CSV2_7)
- SHAPEFILE_1: SHAPEFILE from $(SourceDataset_SHAPEFILE_2)
- CSV2_2: CSV2 from $(SourceDataset_CSV2)

Writers:
- SHAPEFILE_2: SHAPEFILE to $(DestDataset_SHAPEFILE_3)

remove_attribute: AttributeRemover
    REMOVE_ATTRS = AREA,C20002005,maille10_1,Shape_Area,Shape_Leng
    -> grid_geometry_joiner [LEFT]
    -> half_ignorance_score [maille10_grid]
    -> rename_attribute
    -> delete_unsampled_grid_cells [maille10_grid]
remove_srid: AttributeTrimmer
    SRC_ATTRS = geom_wkt
    TRIM_CHARS = SRID=2154;
    TRIM_TO_NONE = Yes
    TRIM_TYPE = BOTH
    -> reproject
reproject: Reprojector
    DEST = EPSG:2154
    INTERPOLATION_TYPE = ,NearestNeighbor
    RASTER_CELL_SIZE_LOOKUP = ,PreserveCells
    RASTER_TOLERANCE = 0.0
    SOURCE = EPSG:2154
    INTERPOLATION_TYPE_NAME = Nearest Neighbor
    RASTER_CELL_SIZE = Preserve Cells
    REPROJECTED -> replace_geom_wkt
replace_geom_wkt: GeometryReplacer
    KIND = wkt
    OGC_WKT_PRECISION = FLOAT_32
    REMOVE_ATTRIBUTE = Yes
    SOURCE = @Value(geom_wkt)
    KIND_LONG = OGC Well Known Text
    OGC_WKT_PRECISION_DISPLAY = 32-bit
    -> join_completeness_ignorance [LEFT]
half_ignorance_score: RCaller
    NEW_ATTRIBUTES = maille10 char(200) geom_wkt char(200) ignoranceindex number(20,10) si number(20,10) species_count number(20,10) NOM_NIV_1 char(200) PERCENTAGE number(20,10) occurrence_count buffer
    QUERY_DEF:
      Output,library(sf)
      library(dplyr)

      #Prepare the datasets
      data <- rename(data, c('maille10' = 'maille'))
      data <- data %>%
        left_join(st_drop_geometry(maille10_grid), by = "maille10")
      data <- data %>%
        filter(PERCENTAGE >= 40)

      #Calculate number of species per grid cell
      number_species <- data %>%
        group_by(maille10) %>%
        summarise(species_count = n_distinct(cd_espece))

      #Calculate number of occurrences per grid cell
      number_occurrences <- data %>%
        group_by(maille10) %>%
        summarise(occurrence_count = n(), .groups = "drop")

      #Join both datasets
      counts <- number_species %>%
        inner_join(number_occurrences, by = "maille10")

      #Calculate half-ignorance score
      counts$si <- counts$occurrence_count / counts$species_count
      counts$ignoranceindex <- 5 / (counts$si +5)

      #Join half-ignorance dataset with grid geometry
      halfignorance <- counts %>%
        left_join(geometry %>% select(maille10, geom_wkt), by = "maille10")

      #Join dataset with biogeographical units
      setwd("")
      unep <- st_read("")

      fmeOutput <- halfignorance %>%
        left_join(st_drop_geometry(unep), by = "maille10")

      ,maille10 char(200) geom_wkt char(200) ignoranceindex number(20,10) si number(20,10) species_count number(20,10) NOM_NIV_1 char(200) PERCENTAGE number(20,10) occurrence_count buffer
    R_SCRIPT:
      library(sf)
      library(dplyr)

      #Prepare the datasets
      data <- rename(data, c('maille10' = 'maille'))
      data <- data %>%
        left_join(st_drop_geometry(maille10_grid), by = "maille10")
      data <- data %>%
        filter(PERCENTAGE >= 40)

      #Calculate number of species per grid cell
      number_species <- data %>%
        group_by(maille10) %>%
        summarise(species_count = n_distinct(cd_espece))

      #Calculate number of occurrences per grid cell
      number_occurrences <- data %>%
        group_by(maille10) %>%
        summarise(occurrence_count = n(), .groups = "drop")

      #Join both datasets
      counts <- number_species %>%
        inner_join(number_occurrences, by = "maille10")

      #Calculate half-ignorance score
      counts$si <- counts$occurrence_count / counts$species_count
      counts$ignoranceindex <- 5 / (counts$si +5)

      #Join half-ignorance dataset with grid geometry
      halfignorance <- counts %>%
        left_join(geometry %>% select(maille10, geom_wkt), by = "maille10")

      #Join dataset with biogeographical units
      setwd("")
      unep <- st_read("")

      fmeOutput <- halfignorance %>%
        left_join(st_drop_geometry(unep), by = "maille10")
    TABLE_DEF = geometry,maille10,varchar(8),geom_wkt,varchar(208),data,oid,integer,cd_espece,integer,date_obs,text,maille,varchar(8),maille10_grid,maille10,varchar(254),PERCENTAGE,double
    -> delete_unsampled_grid_cells_2 [data]
delete_unsampled_grid_cells_2: RCaller
    NEW_ATTRIBUTES = species_count number(20,10) geom_wkt varchar(200) ignoranceindex number(20,10) maille10 varchar(200) si number(20,10) NOM_NIV_1 varchar(200) percentage_region number(20,10) occurrence_count number(20,10)
    QUERY_DEF:
      Output,library(dplyr)

      fmeOutput <- full_join(data, maille10_grid, by = "maille10")

      fmeOutput$ignoranceindex[is.na(fmeOutput$ignoranceindex)] <- 1

      fmeOutput <- fmeOutput %>%
        filter(percentage_region >= 40 <pipe> is.na(percentage_region)),species_count number(20,10) geom_wkt varchar(200) ignoranceindex number(20,10) maille10 varchar(200) si number(20,10) NOM_NIV_1 varchar(200) percentage_region number(20,10) occurrence_count number(20,10)
    R_SCRIPT:
      library(dplyr)

      fmeOutput <- full_join(data, maille10_grid, by = "maille10")

      fmeOutput$ignoranceindex[is.na(fmeOutput$ignoranceindex)] <- 1

      fmeOutput <- fmeOutput %>%
        filter(percentage_region >= 40 <pipe> is.na(percentage_region))
    TABLE_DEF = data,maille10,varchar(200),geom_wkt,varchar(200),ignoranceindex,"real(20,10)",si,"real(20,10)",species_count,"real(20,10)",NOM_NIV_1,varchar(200),PERCENTAGE,"real(20,10)",occurrence_count,text,maille10_grid,percentage_region,double,maille10,varchar(254)
    -> rename_attribute_biogeo_2
rename_attribute_biogeo_2: AttributeRenamer
    ATTR_TABLE = RENAME_SET_DEFAULT NOM_NIV_1 > biogeographical_unit
    KEEP_RENAMED_ONLY = no
    MISSING_INPUT_ATTRS = REMOVE
    -> join_completeness_ignorance [RIGHT]
join_completeness_ignorance: FeatureJoiner
    ATTR_CONFLICT_RES_LOOKUP = USE_LEFT
    GEOMETRY_HANDLING_LOOKUP = USE_LEFT
    JOIN_KEYS = maille10 maille10 AUTO
    JOIN_MODE = Full
    ATTR_CONFLICT_RES = Prefer Left
    GEOMETRY_HANDLING = Prefer Left
    JOINED -> knowledge_score
knowledge_score: ExpressionEvaluator
    ACTION = Create New Attribute
    EXPRESSION = 1-@Value(ignoranceindex)
    VAL_ATTR = knowledgescore
    -> remove_unused_attributes
remove_unused_attributes: AttributeRemover
    REMOVE_ATTRS = PERCENTAGE,Pourcentage,Shape_Area,Shape_Leng,f1,f2,Ni,total_count,chao1_estimate,espececount,AREA,maille10_1
    -> Mammifères (writer SHAPEFILE_2)
Mammifères (writer SHAPEFILE_2)
    attributes: biogeograp varchar(200), chao2_esti number(20,10), expected_s number(20,10), completene number(20,10), maille10 varchar(200), mean_expec number(20,10), occurrence number(20,10), percentage number(20,10), total_spec number(20,10), species_co number(20,10), geom_wkt varchar(200), ignorancei number(20,10), si number(20,10), knowledges double

Bookmark: species data file
CSV (reader CSV2_2)
    attributes: oid uint32, cd_espece uint32, date_obs date, maille varchar(8)
    -> half_ignorance_score [data]
    -> completeness_score [data]

Bookmark: grid cells without marine cells
maille10sansocean (reader SHAPEFILE_1)
    attributes: maille10 varchar(254), maille10_1 varchar(254), AREA double, PERCENTAGE double, C20002005 long, Shape_Leng double, Shape_Area double
    -> remove_attribute

Bookmark: completeness score
rename_attribute: AttributeRenamer
    ATTR_TABLE = RENAME_SET_DEFAULT PERCENTAGE > percentage_region
    KEEP_RENAMED_ONLY = no
    MISSING_INPUT_ATTRS = REMOVE
    -> completeness_score [maille10_grid]
    -> delete_unsampled_grid_cells_2 [maille10_grid]
completeness_score: RCaller
    NEW_ATTRIBUTES = maille10 varchar(200) expected_species number(20,10) chao2_estimate number(20,10) completeness number(20,10) mean_expected number(20,10) NOM_NIV_1 varchar(200) occurrence_count number(20,10) total_species_observed number(20,10) percentage_region number(20,10)
    QUERY_DEF:
      Output,library(dplyr)
      library(readxl)
      library(sf)
      library(tidyverse)
      library(tidyr)
      library(sqldf)
      library(lubridate)

      #Read dataset with biogeographical units
      setwd("")
      unep <- st_read("")

      # Calculate singletons and doubletons per grid cell
      data <- rename(data, c('maille10' = 'maille'))

      data <- data %>%
        mutate(date_obs = as.Date(parse_date_time(date_obs, "ymd")),
               year = year(date_obs))

      species_counts_year <- data %>%
        group_by(maille10, cd_espece) %>%
        summarise(years_observed = n_distinct(year), .groups = "drop")

      singletons <- species_counts_year %>%
        filter(years_observed == 1) %>%
        group_by(maille10) %>%
        summarise(f1 = n(), .groups = "drop") %>%
        complete(maille10 = unique(data$maille10), fill = list(f1 = 0))

      doubletons <- species_counts_year %>%
        filter(years_observed == 2) %>%
        group_by(maille10) %>%
        summarise(f2 = n(), .groups = "drop") %>%
        complete(maille10 = unique(data$maille10), fill = list(f2 = 0))

      # Calculate Chao2 estimator / completeness score per grid cell
      chao2_results <- singletons %>%
        inner_join(doubletons, by = "maille10") %>%
        mutate(chao2_estimate = ((15-1)/15)*(f1*(f1-1))/(2*(f2+1))
        )

      #Get the total number of observed species per grid cell
      total_observed_species <- data %>%
        group_by(maille10) %>%
        summarise(total_species_observed = n_distinct(cd_espece))

      #Join Chao2 estimator and total number of species observed
      completeness_score <- chao2_results %>%
        inner_join(total_observed_species, by = "maille10")

      #Remove duplicate grid cells
      completeness_score <- completeness_score %>%
        distinct()

      #Join completeness scores and biogeographical units per grid cell
      biogeography_completeness <- completeness_score %>%
        left_join(st_drop_geometry(unep), by = "maille10")

      #Get the geometry for each grid cell
      maille10_geometry <- geometry %>%
        filter(maille10 %in% biogeography_completeness$maille10)
      biogeography_completeness <- biogeography_completeness %>%
        left_join(maille10_geometry %>% select(maille10, geom_wkt), by = "maille10")

      #Get the number of occurrences per grid cell
      number_occurrences <- data %>%
        group_by(maille10) %>%
        summarise(occurrence_count = n())

      #Join number of occurrences to completeness dataset
      biogeography_completeness <- biogeography_completeness %>%
        inner_join(number_occurrences, by = "maille10")

      #Get the number of expected species
      biogeography_completeness <- biogeography_completeness %>%
        mutate(expected_species = ifelse(occurrence_count >= 10, total_species_observed + chao2_estimate, NA))

      #Ensure that poorly sampled grid cells are assigned NA
      biogeography_completeness$expected_species[biogeography_completeness$occurrence_count < 10] <- NA

      #Handle NA values and remove cells intersecting less than 40% of the region
      biogeography_completeness <- biogeography_completeness %>%
        filter(maille10 != "E045N628")

      biogeography_completeness <- biogeography_completeness %>%
        left_join(st_drop_geometry(maille10_grid), by = "maille10")

      biogeography_completeness <- biogeography_completeness %>%
        filter(percentage_region >= 40)

      #Calculate mean number of expected species per biogeographical unit
      completeness_scores <- biogeography_completeness %>%
        group_by(NOM_NIV_1) %>%
        summarise(mean_expected = mean(expected_species, na.rm = TRUE)) %>%
        ungroup()

      completeness_scores <- biogeography_completeness %>%
        left_join(completeness_scores, by = "NOM_NIV_1")

      #Get the final completeness score per grid cell
      completeness_scores <- completeness_scores %>%
      mutate(completeness = total_species_observed / mean_expected)

      #Create FME output
      fmeOutput <- completeness_scores
      print(fmeOutput)


      ,maille10 varchar(200) expected_species number(20,10) chao2_estimate number(20,10) completeness number(20,10) mean_expected number(20,10) NOM_NIV_1 varchar(200) occurrence_count number(20,10) total_species_observed number(20,10) percentage_region number(20,10)
    R_SCRIPT:
      library(dplyr)
      library(readxl)
      library(sf)
      library(tidyverse)
      library(tidyr)
      library(sqldf)
      library(lubridate)

      #Read dataset with biogeographical units
      setwd("")
      unep <- st_read("")

      # Calculate singletons and doubletons per grid cell
      data <- rename(data, c('maille10' = 'maille'))

      data <- data %>%
        mutate(date_obs = as.Date(parse_date_time(date_obs, "ymd")),
               year = year(date_obs))

      species_counts_year <- data %>%
        group_by(maille10, cd_espece) %>%
        summarise(years_observed = n_distinct(year), .groups = "drop")

      singletons <- species_counts_year %>%
        filter(years_observed == 1) %>%
        group_by(maille10) %>%
        summarise(f1 = n(), .groups = "drop") %>%
        complete(maille10 = unique(data$maille10), fill = list(f1 = 0))

      doubletons <- species_counts_year %>%
        filter(years_observed == 2) %>%
        group_by(maille10) %>%
        summarise(f2 = n(), .groups = "drop") %>%
        complete(maille10 = unique(data$maille10), fill = list(f2 = 0))

      # Calculate Chao2 estimator / completeness score per grid cell
      chao2_results <- singletons %>%
        inner_join(doubletons, by = "maille10") %>%
        mutate(chao2_estimate = ((15-1)/15)*(f1*(f1-1))/(2*(f2+1))
        )

      #Get the total number of observed species per grid cell
      total_observed_species <- data %>%
        group_by(maille10) %>%
        summarise(total_species_observed = n_distinct(cd_espece))

      #Join Chao2 estimator and total number of species observed
      completeness_score <- chao2_results %>%
        inner_join(total_observed_species, by = "maille10")

      #Remove duplicate grid cells
      completeness_score <- completeness_score %>%
        distinct()

      #Join completeness scores and biogeographical units per grid cell
      biogeography_completeness <- completeness_score %>%
        left_join(st_drop_geometry(unep), by = "maille10")

      #Get the geometry for each grid cell
      maille10_geometry <- geometry %>%
        filter(maille10 %in% biogeography_completeness$maille10)
      biogeography_completeness <- biogeography_completeness %>%
        left_join(maille10_geometry %>% select(maille10, geom_wkt), by = "maille10")

      #Get the number of occurrences per grid cell
      number_occurrences <- data %>%
        group_by(maille10) %>%
        summarise(occurrence_count = n())

      #Join number of occurrences to completeness dataset
      biogeography_completeness <- biogeography_completeness %>%
        inner_join(number_occurrences, by = "maille10")

      #Get the number of expected species
      biogeography_completeness <- biogeography_completeness %>%
        mutate(expected_species = ifelse(occurrence_count >= 10, total_species_observed + chao2_estimate, NA))

      #Ensure that poorly sampled grid cells are assigned NA
      biogeography_completeness$expected_species[biogeography_completeness$occurrence_count < 10] <- NA

      #Handle NA values and remove cells intersecting less than 40% of the region
      biogeography_completeness <- biogeography_completeness %>%
        filter(maille10 != "E045N628")

      biogeography_completeness <- biogeography_completeness %>%
        left_join(st_drop_geometry(maille10_grid), by = "maille10")

      biogeography_completeness <- biogeography_completeness %>%
        filter(percentage_region >= 40)

      #Calculate mean number of expected species per biogeographical unit
      completeness_scores <- biogeography_completeness %>%
        group_by(NOM_NIV_1) %>%
        summarise(mean_expected = mean(expected_species, na.rm = TRUE)) %>%
        ungroup()

      completeness_scores <- biogeography_completeness %>%
        left_join(completeness_scores, by = "NOM_NIV_1")

      #Get the final completeness score per grid cell
      completeness_scores <- completeness_scores %>%
      mutate(completeness = total_species_observed / mean_expected)

      #Create FME output
      fmeOutput <- completeness_scores
      print(fmeOutput)
    TABLE_DEF = geometry,maille10,varchar(8),geom_wkt,varchar(208),data,oid,integer,cd_espece,integer,date_obs,text,maille,varchar(8),maille10_grid,percentage_region,double,maille10,varchar(254)
    -> delete_unsampled_grid_cells [data]
delete_unsampled_grid_cells: RCaller
    NEW_ATTRIBUTES = chao2_estimate number(20,10) expected_species number(20,10) completeness number(20,10) maille10 varchar(200) mean_expected number(20,10) NOM_NIV_1 varchar(200) occurrence_count number(20,10) percentage_region number(20,10) total_species_observed number(20,10)
    QUERY_DEF:
      Output,library(dplyr)

      fmeOutput <- full_join(data, maille10_grid, by = "maille10")

      fmeOutput$completeness[is.na(fmeOutput$completeness)] <- 0

      fmeOutput <- fmeOutput %>%
        filter(percentage_region >= 40 <pipe> is.na(percentage_region))
      ,chao2_estimate number(20,10) expected_species number(20,10) completeness number(20,10) maille10 varchar(200) mean_expected number(20,10) NOM_NIV_1 varchar(200) occurrence_count number(20,10) percentage_region number(20,10) total_species_observed number(20,10)
    R_SCRIPT:
      library(dplyr)

      fmeOutput <- full_join(data, maille10_grid, by = "maille10")

      fmeOutput$completeness[is.na(fmeOutput$completeness)] <- 0

      fmeOutput <- fmeOutput %>%
        filter(percentage_region >= 40 <pipe> is.na(percentage_region))
    TABLE_DEF = data,maille10,varchar(200),expected_species,"real(20,10)",chao2_estimate,"real(20,10)",completeness,"real(20,10)",mean_expected,"real(20,10)",NOM_NIV_1,varchar(200),occurrence_count,"real(20,10)",total_species_observed,"real(20,10)",percentage_region,"real(20,10)",maille10_grid,maille10,varchar(254),PERCENTAGE,double
    -> rename_attribute_biogeo
rename_attribute_biogeo: AttributeRenamer
    ATTR_TABLE = RENAME_SET_DEFAULT NOM_NIV_1 > biogeographical_unit
    KEEP_RENAMED_ONLY = no
    MISSING_INPUT_ATTRS = REMOVE
    -> geometry_joiner [LEFT]
grid_geometry_joiner: FeatureJoiner
    ATTR_CONFLICT_RES_LOOKUP = USE_LEFT
    GEOMETRY_HANDLING_LOOKUP = USE_LEFT
    JOIN_KEYS = maille10 maille10 AUTO
    JOIN_MODE = Inner
    ATTR_CONFLICT_RES = Prefer Left
    GEOMETRY_HANDLING = Prefer Left
    JOINED -> geometry_joiner [RIGHT]
geometry_joiner: FeatureJoiner
    ATTR_CONFLICT_RES_LOOKUP = USE_RIGHT
    GEOMETRY_HANDLING_LOOKUP = USE_LEFT
    JOIN_KEYS = maille10 maille10 AUTO
    JOIN_MODE = Left
    ATTR_CONFLICT_RES = Prefer Right
    GEOMETRY_HANDLING = Prefer Left
    JOINED -> remove_srid

Bookmark: grid cells geometry
CSV (reader CSV2_1)
    attributes: maille10 varchar(8), geom_wkt varchar(208)
    -> half_ignorance_score [geometry]
    -> completeness_score [geometry]
    -> grid_geometry_joiner [RIGHT]
